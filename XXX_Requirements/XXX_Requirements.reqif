# SpecRichText

# Specification: XXX Requirements Document
- ReqIF.Description: XXX Requirements Document

## 22: POWER REQUIREMENTS (Headline Type)

### 16: Power lost safe (Requirement Type)
The shall not be damaged if a power failure happens.
- IE PUID: TRT-REQ-16
- SpecRealtion Type -> TRT-REQ-8

### TRT-REQ-8: Communicate Interruption (Requirement Type)
The device shall communicate every kind of power failures.

## 15: PERFORMANCE REQUIREMENTS (Headline Type)

### TRT-REQ-9: BootUP Speed (Requirement Type)
The device shall boot up very fast.

## 16: MECHANICAL REQUIREMENTS (Headline Type)

### TRT-REQ-10: Vibrations (Requirement Type)
The device shall be able to resist 5g acceleration forces.

### 22: Acceleration (Requirement Type)
Acceleration forces should reflect the transport forces.
- IE PUID: TRT-REQ-14

### 14: Humidity (Requirement Type)
The device shall be equiped with an humidity sensor.
- IE PUID: TRT-REQ-11

### 15: Weight (Requirement Type)
The device shall not be so heavy
- IE PUID: TRT-REQ-6

# Specification: XXX Software Reqs
- ReqIF.Description: XXX Software

## 19: Software Ergonomics (Headline Type)

### 20: Easy of Use (Requirement Type)
The software is easy to use
- IE PUID: TRT-REQ-12

### 21: Updates (Requirement Type)
There should be an easy way to do updates
- IE PUID: TRT-REQ-13

### 23: OS Version (Requirement Type)
OS Version shall be a LTS one.
- IE PUID: TRT-REQ-15
